import os,sys,json,math,traceback
from pathlib import Path
import FreeCAD as App,FreeCADGui as Gui,Part,TechDrawGui

ROOT=Path(__file__).resolve().parents[3]
OUT=ROOT/'experiments'/'family-house';WORK=Path(__file__).resolve().parent
if str(WORK) not in sys.path: sys.path.insert(0,str(WORK))
import bim_builder_lib,importlib
importlib.reload(bim_builder_lib)
target_normalized=os.path.normcase(os.path.normpath(str(OUT/'4人家族の平屋_BIM.FCStd')))
doc=next((d for d in App.listDocuments().values() if d.FileName and os.path.normcase(os.path.normpath(d.FileName))==target_normalized),None) or App.getDocument('Family_House_3LDK')
App.setActiveDocument(doc.Name)
spec=json.loads((OUT/'house-design.json').read_text(encoding='utf-8-sig'))
cfg=spec['building'];x0,y0,x1,y1=cfg['outer_bbox'];ff=cfg['finished_floor_level']
envelope=next(o for o in doc.Objects if 'DesignIDs' in o.PropertiesList)
roof=next(o for o in doc.Objects if getattr(getattr(o,'Proxy',None),'Type',None)=='Roof')
opening_map={o.DesignID:o for o in doc.Objects if 'DesignID' in o.PropertiesList and getattr(getattr(o,'Proxy',None),'Type',None)=='Window'}

for opening in spec['openings']:
    opening_map[opening['id']].Normal=App.Vector(0,-1,0) if opening['axis']=='x' else App.Vector(1,0,0)
roof.Runs=[min(x1-x0,y1-y0)/2]*4
if doc.getObject('FoundationReference') is None:
    outer=Part.Face(Part.makePolygon([App.Vector(x0,y0,0),App.Vector(x1,y0,0),App.Vector(x1,y1,0),App.Vector(x0,y1,0),App.Vector(x0,y0,0)]))
    inner=Part.Face(Part.makePolygon([App.Vector(x0+200,y0+200,0),App.Vector(x1-200,y0+200,0),App.Vector(x1-200,y1-200,0),App.Vector(x0+200,y1-200,0),App.Vector(x0+200,y0+200,0)]))
    obj=doc.addObject('Part::Feature','FoundationReference');obj.Label='基礎立上り参考 - 構造形式・地盤・配筋・寸法未検証'
    obj.Shape=outer.cut(inner).extrude(App.Vector(0,0,300));obj.ViewObject.ShapeColor=(.53,.55,.56)
    doc.Structure.addObject(obj)
    bim_builder_lib.metadata(obj,'ReferenceOnly','Foundation appearance reference GL0..300 only; ground, reinforcement, base slab, structural type and dimensions are not designed. Not for construction or quantity take-off.')
doc.recompute()

def show_original():
    doc.Technical.Visibility=False
    for obj in doc.Technical.Group: obj.Visibility=False
    for obj in doc.Walls.Group: obj.Visibility=True
    for obj in doc.Openings.Group: obj.Visibility=getattr(obj,'IfcType','')!='Opening Element'
    for obj in doc.Furniture.Group: obj.Visibility=True
    for obj in doc.Structure.Group: obj.Visibility=True
    for obj in doc.Spaces.Group: obj.Visibility=False
    roof.Visibility=True
    for obj in doc.Objects:
        if obj.Name.endswith('RoomVolume') or obj.TypeId=='Sketcher::SketchObject': obj.Visibility=False
    Gui.Selection.clearSelection();Gui.updateGui()

show_original()
cameras={'exterior':bim_builder_lib.camera_view(doc,(1,-1,1),OUT/'exterior.png',(1600,1100))}
for key,direction in [('south',(0,-1,0)),('north',(0,1,0)),('east',(1,0,0)),('west',(-1,0,0))]:
    cameras[key]=bim_builder_lib.camera_view(doc,direction,OUT/(key+'-elevation.png'))

for obj in doc.Walls.Group: obj.Visibility=False
for obj in doc.Openings.Group: obj.Visibility=False
roof.Visibility=False
doc.Technical.Visibility=True
for obj in doc.Technical.Group: obj.Visibility=obj.Name.startswith('PlanCut_') and hasattr(obj,'Shape') and not obj.Shape.isNull()
cameras['cutaway']=bim_builder_lib.camera_view(doc,(1,-1,1.3),OUT/'cutaway.png',(1800,1300))
cameras['plan']=bim_builder_lib.camera_view(doc,(0,0,1),OUT/'plan-model.png',(1600,1200))
show_original()

dimensions=bim_builder_lib.dimension_from_envelope(doc,doc.FloorPlan_A3,doc.PlanView,doc.getObject('PlanCut_'+envelope.Name),x1-x0,y1-y0)
svg_unit_gate=bim_builder_lib.export_plan_svg_mm(doc,doc.FloorPlan_A3,OUT/'native-floor-plan.svg')
report=json.loads((OUT/'native-model-verification.json').read_text(encoding='utf-8'))
report['status']='pass'
report['contour_dimension_gate']=dimensions
report['dimension_units_gate']=svg_unit_gate
report['native_dimensions']=[{'name':o.Name,'value_mm':o.getRawValue(),'state':o.State} for o in doc.Objects if o.TypeId=='TechDraw::DrawViewDimension']
report['camera_views']=cameras
report['roof_coverage']=[]
for x in [200,3125,6050,8975,11900]:
    for y in [200,2375,4550,6725,8900]:
        hit=roof.Shape.common(Part.makeLine(App.Vector(x,y,0),App.Vector(x,y,10000)))
        report['roof_coverage'].append({'xy_mm':[x,y],'intersects':not hit.isNull() and hit.Length>0,'common_length_mm':hit.Length if not hit.isNull() else 0})
assert all(r['intersects'] for r in report['roof_coverage'])
report['roof_geometry']={'native_type':roof.Proxy.Type,'valid':roof.Shape.isValid(),'runs_mm':list(roof.Runs),'pitch_degrees':list(roof.Angles),'volume_m3':roof.Shape.Volume/1e9,'coverage_pass_count':sum(r['intersects'] for r in report['roof_coverage'])}
report['opening_frame_host_checks']=[]
for opening in spec['openings']:
    obj=opening_map[opening['id']]
    if obj.Shape.isNull():
        report['opening_frame_host_checks'].append({'id':opening['id'],'shape':'No leaf/frame by design','pass':opening['kind']=='passage'})
        continue
    host=next(w for w in spec['walls'] if w['id']==opening['host']);t=host['thickness'];cx,cy=opening['center'];bb=obj.Shape.BoundBox
    actual=[bb.YMin,bb.YMax] if opening['axis']=='x' else [bb.XMin,bb.XMax]
    intended=[cy-t/2,cy+t/2] if opening['axis']=='x' else [cx-t/2,cx+t/2]
    okay=actual[0]>=intended[0]-1e-5 and actual[1]<=intended[1]+1e-5
    report['opening_frame_host_checks'].append({'id':opening['id'],'actual_normal_extent_mm':actual,'host_normal_extent_mm':intended,'pass':okay})
assert all(r['pass'] for r in report['opening_frame_host_checks'])
wall_rows=[]
for obj in doc.Walls.Group:
    ids=obj.DesignIDs.split(',') if 'DesignIDs' in obj.PropertiesList else [obj.DesignID]
    entries=[w for w in spec['walls'] if w['id'] in ids]
    if len(entries)>1:
        initial=((x1-x0)*(y1-y0)-(x1-x0-400)*(y1-y0-400))*2850
    else:
        w=entries[0];initial=math.dist(w['start'],w['end'])*w['thickness']*(w['top_level']-w['base_level'])
    cuts=0
    for opening in spec['openings']:
        if opening['host'] not in ids: continue
        w=next(w for w in entries if w['id']==opening['host'])
        bottom=ff+opening['sill'];cutheight=max(0,min(bottom+opening['height'],w['top_level'])-max(bottom,w['base_level']))
        cuts+=opening['width']*cutheight*w['thickness']
    expected=initial-cuts
    row={'object':obj.Name,'design_ids':ids,'expected_volume_after_cut_mm3':expected,'actual_volume_after_cut_mm3':obj.Shape.Volume,'pass':abs(obj.Shape.Volume-expected)<max(1,expected*1e-8)}
    wall_rows.append(row)
assert all(r['pass'] for r in wall_rows),wall_rows
report['final_wall_cut_volume_checks']=wall_rows
report['foundation_reference']={'ReferenceOnly':True,'bottom_mm':0,'top_mm':300,'statement':doc.FoundationReference.ReferenceOnly}
report['door_actual_operable_width']='Unverified product/opening operation. Native 3D door panels are closed-state single leaf; frame span is not asserted as actual opening width.'
report['default_view']='Roof-on orthographic axonometric exterior; use Roof group visibility and technical cut objects for cutaway'
report['shapes']=[{'object':o.Name,'label':o.Label,'type':o.TypeId,'native_bim_type':getattr(getattr(o,'Proxy',None),'Type',None),'valid':o.Shape.isValid(),'solids':len(o.Shape.Solids),'volume_mm3':o.Shape.Volume} for o in doc.Objects if hasattr(o,'Shape') and not o.Shape.isNull()]
assert all(r['valid'] for r in report['shapes'])
assert abs(doc.BuildingWidth.getRawValue()-12100)<1e-5 and abs(doc.BuildingDepth.getRawValue()-9100)<1e-5
(OUT/'native-model-verification.json').write_text(json.dumps(report,ensure_ascii=False,indent=2),encoding='utf-8')
doc.FloorPlan_A3.ViewObject.Visibility=False
bim_builder_lib.camera_view(doc,(1,-1,1),OUT/'exterior.png',(1600,1100))
doc.recompute();doc.save()
print(json.dumps({'document':doc.Name,'file':doc.FileName,'roof_coverage':25,'dimensions_mm':[doc.BuildingWidth.getRawValue(),doc.BuildingDepth.getRawValue()],'all_window_frames_in_host':True,'all_host_volumes_match':True,'shape_count':len(report['shapes']),'status':'pass'},ensure_ascii=False))
